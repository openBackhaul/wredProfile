module wred-profile-1-0 {
  yang-version 1.1;
  namespace "urn:onf:yang:wred-profile-1-0";
  prefix wred-profile;

  import ietf-yang-types {
    prefix yang;
  }
  import core-model-1-4 {
    prefix core-model;
  }

  organization
    "openBackhaul.com proposal to Open Networking Foundation (ONF)";
  contact
    "WG Web : https://github.com/openBackhaul/Overview
     WG List: WredProfile@openBackhaul.com
     Editor : Thorsten Heinze
     Email  : Thorsten.Heinze@openBackhaul.com";
  description
    "Technology specific definition for WRED (Weighted Random Early Detection) profiles that can be referenced by multiple interface instances.

     Copyright 2024 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2024-01-04 {
    description
      "Model for the Transport SDN Introduction at Telefonica Germany.
       Please view https://github.com/openBackhaul/wredProfile/issues for changes.";
    reference
      "https://github.com/openBackhaul/wredProfile/tree/tsi: Model definition
       https://github.com/openBackhaul/onfCoreIm/tree/tsi: ONF TR-512 Core IM incl. Profile and enhanced Equipment definition";
  }
  revision 2022-03-30 {
    description
      "Model for the Transport SDN Pilot at Telefonica Germany.
       Please view https://github.com/openBackhaul/wredProfile/issues for changes.";
    reference
      "https://github.com/openBackhaul/wredProfile/tree/tsi: Model definition
       https://github.com/openBackhaul/onfCoreIm/tree/tsi: ONF TR-512 Core IM incl. Profile and enhanced Equipment definition";
  }
  revision 2020-01-24 {
    description
      "Model for the Transport SDN Pilot at Telefonica Germany.
       Please view https://github.com/openBackhaul/wredProfile/issues for changes.";
    reference
      "https://github.com/openBackhaul/wredProfile/tree/tsi: Model definition
       https://github.com/openBackhaul/onfCoreIm/tree/tsi: ONF TR-512 Core IM incl. Profile and enhanced Equipment definition";
  }
  revision 2019-07-12 {
    description
      "Model for the Transport SDN Pilot at Telefonica Germany.
       Please view https://github.com/openBackhaul/wredProfile/issues for changes.";
    reference
      "https://github.com/openBackhaul/wredProfile/tree/tsi: Model definition
       https://github.com/openBackhaul/onfCoreIm/tree/tsi: ONF TR-512 Core IM incl. Profile and enhanced Equipment definition";
  }

  identity PROFILE_NAME_TYPE_WRED_PROFILE {
    base core-model:PROFILE_NAME_TYPE;
    description
      "none";
  }

  /****************************************
   * grouping statements for object classes
   **************************************/ 

  grouping wred-profile-spec {
    description
      "none";
    container wred-profile-pac {
      description
        "none";
      uses wred-profile-pac;
    }
  }

  grouping wred-profile-pac {
    description
      "none";
    container wred-profile-capability {
      config false;
      description
        "none";
      uses wred-profile-capability;
    }
    container wred-profile-configuration {
      config false;
      description
        "none";
      uses wred-profile-configuration;
    }
  }

  grouping wred-profile-capability {
    description
      "none";
    leaf available-buffer-size {
      type int32;
      units "Byte";
      default "-1";
      config false;
      description
        "Maximum value that could be configured as thresholdHigh in Byte.";
    }
    leaf drop-probability-at-threshold-low-is-avail {
      type boolean;
      default "false";
      config false;
      description
        "true = It is possible to set a drop probability at the lower threshold.";
    }
    leaf gentle-wred-is-avail {
      type boolean;
      default "false";
      config false;
      description
        "true = The device allows activating a linear increase of drop probability between dropProbabilityAtThresholdHigh and 100% at thresholdGentle (usually drop probability jumps to 100% at thresholdHigh).";
    }
    leaf sensitivity-setting-is-avail {
      type boolean;
      default "false";
      config false;
      description
        "true = It is possible to set the sensitivity for the burst size.";
    }
    leaf coloring-is-avail {
      type boolean;
      default "false";
      config false;
      description
        "true = The device allows marking exceeding packets yellow instead of immediately discarding them.";
    }
  }

  grouping wred-profile-configuration {
    description
      "none";
    leaf external-label {
      type string;
      default "External label not yet defined.";
      config false;
      description
        "Identifier of the instance of WredProfile. Could be a name, could be a number. Free text field to be filled by the operator.";
    }
    leaf threshold-low {
      type int32;
      units "Byte";
      default "-1";
      config false;
      description
        "Defines the lower threshold in Byte. When average queue content is exceeding this value, packets start getting dropped. Probability of dropping is linear increasing until it reaches the value configured in dropProbabilityAtThresholdHigh when average queue content reaches thresholdHigh.";
    }
    leaf drop-probability-at-threshold-low {
      type int8;
      units "%";
      default "-1";
      config false;
      description
        "Only relevant if (dropProbabilityAtLowThresholdIsAvail==true). Defines the probability (as a percentage) of an incoming packet getting dropped when the content of the queue reaches the low threshold.";
    }
    leaf threshold-high {
      type int32;
      units "Byte";
      default "-1";
      config false;
      description
        "Defines the upper threshold in Byte.  When average queue content is reaching this value, incoming packets are dropped with the probability configured in dropProbabilityAtThresholdHigh. When average queue content is exceeding this value, all incoming packets get dropped.";
    }
    leaf drop-probability-at-threshold-high {
      type int8;
      units "%";
      default "-1";
      config false;
      description
        "Defines the probability (as a percentage) of an incoming packet getting dropped when the content of the queue reaches the upper threshold.";
    }
    leaf gentle-wred-is-on {
      type boolean;
      default "false";
      config false;
      description
        "Only relevant if (gentleWredIsAvail==true). true = The drop probability is linear increasing between dropProbabilityAtThresholdHigh and 100% at thresholdGentle (otherwise drop probability jumps to 100% at thresholdHigh).";
    }
    leaf threshold-gentle {
      type int32;
      units "Byte";
      default "-1";
      config false;
      description
        "Only relevant if (gentleWredIsAvail==true) AND (gentleWredIsOn==true). Defines the 100% dropping threshold for gentle WRED in Byte.  When average queue content reaches or exceeds this value, incoming packets get dropped with 100% probability.";
    }
    leaf sensitivity {
      type int8;
      units "%";
      default "-1";
      config false;
      description
        "Only relevant if (sensitivitySettingIsAvail==true). Defines how sensitive WRED reacts on traffic burst. low values = WRED reacts quickly and is sensitive to short bursts. high values = WRED reacts slowly on short bursts, which could result in buffer overflow and tail drop. Values between 0 and 15.";
    }
    leaf coloring-is-on {
      type boolean;
      default "false";
      config false;
      description
        "Only relevant if (coloringIsAvail==true). true = Exceeding packets are marked yellow instead of being immediately discarded.";
    }
  }

  /****************************************
   * package interfaces
   **************************************/ 

  rpc create-wred-profile {
    description
      "none";
    input {
      leaf external-label {
        type string;
        mandatory true;
        description
          "Identifier of the instance of WredProfile. Could be a name, could be a number. Free text field to be filled by the operator.";
      }
      leaf threshold-low {
        type uint64;
        mandatory true;
        description
          "Defines the lower threshold in Byte. When average queue content is exceeding this value, packets start getting dropped. Probability of dropping is linear increasing until it reaches the value configured in dropProbabilityAtThresholdHigh when average queue content reaches thresholdHigh.";
      }
      leaf drop-probability-at-threshold-low {
        type uint64;
        mandatory true;
        description
          "Only relevant if (dropProbabilityAtLowThresholdIsAvail==true). Defines the probability (as a percentage) of an incoming packet getting dropped when the content of the queue reaches the low threshold.";
      }
      leaf threshold-high {
        type uint64;
        mandatory true;
        description
          "Defines the upper threshold in Byte. When average queue content is reaching this value, incoming packets are dropped with the probability configured in dropProbabilityAtThresholdHigh. When average queue content is exceeding this value, all incoming packets get dropped.";
      }
      leaf drop-probability-at-threshold-high {
        type uint64;
        mandatory true;
        description
          "Defines the probability (as a percentage) of an incoming packet getting dropped when the content of the queue reaches the upper threshold.";
      }
      leaf gentle-wred-is-on {
        type boolean;
        mandatory true;
        description
          "Only relevant if (gentleWredIsAvail==true). true = The drop probability is linear increasing between dropProbabilityAtThresholdHigh and 100% at thresholdGentle (otherwise drop probability jumps to 100% at thresholdHigh).";
      }
      leaf threshold-gentle {
        type uint64;
        mandatory true;
        description
          "Only relevant if (gentleWredIsAvail==true) AND (gentleWredIsOn==true). Defines the 100% dropping threshold for gentle WRED in Byte. When average queue content reaches or exceeds this value, incoming packets get dropped with 100% probability.";
      }
      leaf sensitivity {
        type uint64;
        mandatory true;
        description
          "Only relevant if (sensitivitySettingIsAvail==true). Defines how sensitive WRED reacts on traffic burst. low values = WRED reacts quickly and is sensitive to short bursts. high values = WRED reacts slowly on short bursts, which could result in buffer overflow and tail drop. Values between 0 and 15.";
      }
      leaf coloring-is-on {
        type boolean;
        mandatory true;
        description
          "Only relevant if (coloringIsAvail==true). true = Exceeding packets are marked yellow instead of being immediately discarded.";
      }
    }
    output {
      leaf created-wred-profile {
        type leafref {
          path "/core-model:control-construct/core-model:profile-collection/core-model:profile/core-model:uuid";
          require-instance false;
        }
        mandatory true;
        description
          "UUID of the instance of WredProfile that has been newly created.";
      }
    }
  }

  rpc modify-wred-profile {
    description
      "none";
    input {
      leaf wred-profile-to-be-modified {
        type leafref {
          path "/core-model:control-construct/core-model:profile-collection/core-model:profile/core-model:uuid";
          require-instance false;
        }
        mandatory true;
        description
          "UUID of the instance of WredProfile (ProfileNameType==PROFILE_NAME_TYPE_WRED_PROFILE) that shall be modified.";
      }
      leaf external-label {
        type string;
        description
          "Identifier of the instance of WredProfile. Could be a name, could be a number. Free text field to be filled by the operator.";
      }
      leaf threshold-low {
        type uint64;
        description
          "Defines the lower threshold in Byte. When average queue content is exceeding this value, packets start getting dropped. Probability of dropping is linear increasing until it reaches the value configured in dropProbabilityAtThresholdHigh when average queue content reaches thresholdHigh.";
      }
      leaf drop-probability-at-threshold-low {
        type uint64;
        description
          "Only relevant if (dropProbabilityAtLowThresholdIsAvail==true). Defines the probability (as a percentage) of an incoming packet getting dropped when the content of the queue reaches the low threshold.";
      }
      leaf threshold-high {
        type uint64;
        description
          "Defines the upper threshold in Byte. When average queue content is reaching this value, incoming packets are dropped with the probability configured in dropProbabilityAtThresholdHigh. When average queue content is exceeding this value, all incoming packets get dropped.";
      }
      leaf drop-probability-at-threshold-high {
        type uint64;
        description
          "Defines the probability (as a percentage) of an incoming packet getting dropped when the content of the queue reaches the upper threshold.";
      }
      leaf gentle-wred-is-on {
        type boolean;
        description
          "Only relevant if (gentleWredIsAvail==true). true = The drop probability is linear increasing between dropProbabilityAtThresholdHigh and 100% at thresholdGentle (otherwise drop probability jumps to 100% at thresholdHigh).";
      }
      leaf threshold-gentle {
        type uint64;
        description
          "Only relevant if (gentleWredIsAvail==true) AND (gentleWredIsOn==true). Defines the 100% dropping threshold for gentle WRED in Byte. When average queue content reaches or exceeds this value, incoming packets get dropped with 100% probability.";
      }
      leaf sensitivity {
        type uint64;
        description
          "Only relevant if (sensitivitySettingIsAvail==true). Defines how sensitive WRED reacts on traffic burst. low values = WRED reacts quickly and is sensitive to short bursts. high values = WRED reacts slowly on short bursts, which could result in buffer overflow and tail drop. Values between 0 and 15.";
      }
      leaf coloring-is-on {
        type boolean;
        description
          "Only relevant if (coloringIsAvail==true). true = Exceeding packets are marked yellow instead of being immediately discarded.";
      }
    }
  }

  rpc delete-wred-profile {
    description
      "none";
    input {
      leaf obsolete-wred-profile {
        type leafref {
          path "/core-model:control-construct/core-model:profile-collection/core-model:profile/core-model:uuid";
          require-instance false;
        }
        mandatory true;
        description
          "UUID of the instance of WredProfile (ProfileNameType==PROFILE_NAME_TYPE_WRED_PROFILE) that shall be deleted.";
      }
    }
  }

  augment "/core-model:control-construct/core-model:profile-collection/core-model:profile" {
    when "derived-from-or-self(./core-model:profile-name, 'wred-profile:PROFILE_NAME_TYPE_WRED_PROFILE')";
    description
      "none";
    uses wred-profile-spec;
  }
}
